module intrusiondetection {

  namespace "http://netconfcentral.org/ns/intrusiondetection";

  prefix "intrusion";
  
  description "YANG module for Intrusion Detection System";
  
  revision 2016-06-23 {
    description "Intrusion Detection System";
  }

  typedef roomStatus {
      type enumeration {
        enum occupied{
            value 1;
            description "The room is occupied";
        }
        enum unoccupied {
            value 2;
            description "The room is unoccupied";
        }
      }
   }
   
  grouping room {
    leaf doorsensorID {
      type string;
      description "ID of door sensor in the room";
    }
    leaf motionsensorID {
      type string;
      description "ID of motion sensor in the room";
    }
    leaf status {
       type roomStatus;
    }
  }
  
  container intrusiondetection {
    presence "Indicates the service is available";
    description "Top-level container for all system objects.";
      
    leaf systemID {
      type string;
      config false;
      mandatory true;
      description "ID of the system";
    }
    leaf systemLocation {
      type string;
      config false;
      mandatory true;
      description "The location of the system";
  }
    leaf systemStatus {
      type enumeration {
        enum up {
        value 1;
        description "The system is powered up";
        }
        enum down {
        value 2;
        description "The system is powered down";
        }
        enum armed {
        value 3;
        description "System is armed";
        }
        enum disarmed {
        value 4;
        description "System is disarmed";
        }
      }
      config false;
      mandatory true;
      description "This variable indicates the current state of the system";
    }
    container sensors {
    uses room;
    config false;
  }
  }
  
  rpc armsystem {
    description "Arm the system";
  }
  
  rpc disarmsystem {
    description "Disarm the system";
  }
  
  /*notification systemArmed {
    description "Indicates that system has been armed.";
  
  leaf armStatus {
    description "Indicates the system arming status";
      type enumeration {
        enum armed {
        description "The system was armed.";
        }
        enum disarmed {
        description "The system was disarmed.";
        }
        enum error {
        description "The system is broken";
        }
      }
    }
  }*/
}
